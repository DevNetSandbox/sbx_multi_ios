module dmvpn {

  namespace "http://example.com/dmvpn";
  prefix dmvpn;

  import ietf-inet-types {
    prefix inet;
  }
  import tailf-common {
    prefix tailf;
  }
  import tailf-ncs {
    prefix ncs;
  }

  description
    "Bla bla...";

  revision 2016-01-01 {
    description
      "Initial revision.";
  }

  container action {
    tailf:action double {
      tailf:actionpoint dmvpn-action;
      input {
        leaf number {
          type uint8;
        }
      }
      output {
        leaf result {
          type uint16;
        }
      }
    }
  }
  list dmvpn {
    description "This is an RFS skeleton service";

    key name;
    leaf name {
      tailf:info "Unique service id";
      tailf:cli-allow-range;
      type string;
    }

    uses ncs:service-data;
    ncs:servicepoint dmvpn-servicepoint;

    leaf lan-pool {
      description
        "This pool is used to pull the /29 lan interfaces of remote routers from";
      type inet:ipv4-prefix;
      mandatory true;
    }


    leaf tunnel-pool {
      description
        "This pool is used to allocate the Tunnel interface IP addresses";
      type inet:ipv4-prefix;
      mandatory true;
    }

    leaf tunnel_key {
      type uint8;
      mandatory true;
    }
    leaf tunnel_number {
      type uint8;
      mandatory true;
    }
    leaf nhrp_authentication_key {
      type string;
      mandatory true;
    }
    leaf psk {
      /* TODO implement complexity rules */
      type string;
      mandatory true;
    }
    leaf eigrp_process {
      mandatory true;
      type uint16;
    }

    leaf dns_server {
      type inet:ipv4-address;
      default "8.8.8.8";
    }

    container primary_headend {
      leaf device {
        type leafref {
          path "/ncs:devices/ncs:device/ncs:name";
        }
      }
      leaf vrf {
        type string;
        default "Internet";
      }

      container public-interface {
        leaf type {
          type string;
          default "GigabitEthernet";
        }
        leaf number {
          default "2";
          type string;
        }
      }
    }

    leaf secondary_headend {
      type leafref {
        path "/ncs:devices/ncs:device/ncs:name";
      }
    }

    list remotes {
      key device;
      leaf device {
        type leafref {
          path "/ncs:devices/ncs:device/ncs:name";
        }
      }
      container public-interface {
        leaf type {
          type string;
          default "GigabitEthernet";
        }
        leaf number {
          default "2";
          type string;
        }
      }
      container lan-interface {
        leaf type {
          type string;
          default "GigabitEthernet";
        }
        leaf number {
          default "3";
          type string;
        }
      }
    }
  }
}
