module vpc-distribution {

  namespace "http://example.com/vpc-distribution";
  prefix vpc-distribution;

  import ietf-inet-types {
    prefix inet;
  }
  import tailf-common {
    prefix tailf;
  }
  import tailf-ncs {
    prefix ncs;
  }

  description
    "Bla bla...";

  revision 2016-01-01 {
    description
      "Initial revision.";
  }

  container action {
    tailf:action double {
      tailf:actionpoint vpc-distribution-action;
      input {
        leaf number {
          type uint8;
        }
      }
      output {
        leaf result {
          type uint16;
        }
      }
    }
  }
  list vpc-distribution {
    description "NSO Service Model for VPC Distribution Block with L3 SVI Support";

    key name;
    leaf name {
      tailf:info "Unique service id";
      tailf:cli-allow-range;
      type string;
    }

    leaf aggregate-prefix {
      description
        "This pool is used to pull the /24's needed for VLANs, this prefix is also
        advertised northbound of the distribution block";
      type inet:ipv4-prefix;
      mandatory true;
    }

    // TODO: limit to two devices
    list distribution {
      // For user-sorted lists, operations are defined
      // for manipulating the order of the list entries
      ordered-by user;
      max-elements 2;
      key device;
      leaf device {
        type leafref {
          path "/ncs:devices/ncs:device/ncs:name";
        }
      }
      list connection-to {
        key switch;
        leaf switch {
          type leafref {
            // top down or bottom up?
            path "../../../access_pair/switches/device";
            /* path "../../../../distribution/device"; */
          }
        }

        leaf interface {
          type string;
          // TODO: FORMAT CONTROL
        }
      }

    }

    list access_pair {
      key name;
      leaf name {
        type string;
      }


      list switches {
        ordered-by user;
        max-elements 2;
        key device;

        leaf device {
          type leafref {
            path "/ncs:devices/ncs:device/ncs:name";
          }
        }

        list connection-to {
          key distribution;
          leaf distribution {
            type leafref {
              // top down or bottom up?
              path "/vpc-distribution:vpc-distribution/vpc-distribution:distribution/device";
              /* path "../../../../distribution/device"; */
            }
          }

          leaf interface {
            type string;
            // TODO: FORMAT CONTROL
          }
        }
      }
    }

    


    uses ncs:service-data;
    ncs:servicepoint vpc-distribution-servicepoint;

  }
}
